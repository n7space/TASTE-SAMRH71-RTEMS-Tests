TEST-SPW-DATAVIEW DEFINITIONS ::=
BEGIN

  MyInteger ::= INTEGER (0 .. 10000)
  MyOctStr    ::= OCTET STRING (SIZE (8192))

  MySeq       ::= SEQUENCE {
      -- dummy test data
      test-id             MyInteger,
      test-destination-id MyInteger,
      test-data           MyOctStr
  }

END
