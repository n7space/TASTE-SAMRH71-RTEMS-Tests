SAMRH71-RTEMS-CAN-STATIC-DATAVIEW DEFINITIONS ::=
BEGIN

   MyInteger ::= INTEGER (0 .. 10000)

   Can-Id ::= INTEGER (0 .. 4294967295)

   Can-Frame ::= SEQUENCE {
      id Can-Id,
      data MyInteger
   }

   DataArray ::= SEQUENCE (SIZE (24)) OF MyInteger

   LargeMessage ::= SEQUENCE {
      buffer DataArray,
      coefficient MyInteger
   }

END
