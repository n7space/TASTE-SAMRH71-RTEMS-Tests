SAMRH71-RTEMS-CAN-ADAPTER-DATAVIEW DEFINITIONS ::=
BEGIN

   MyInteger ::= INTEGER (0 .. 10000)
   SmallInteger ::= INTEGER (0 .. 127)

   Can-Standard-Id ::= INTEGER (0 .. 2047)
   Can-Extended-Id ::= INTEGER (0 .. 536870911)

   Can-Id ::= CHOICE {
      standard-id Can-Standard-Id,
      extended-id Can-Extended-Id
   }

   Can-Id-Wrapper ::= SEQUENCE {
      id Can-Id
   }

   Can-Frame ::= SEQUENCE {
      id Can-Id-Wrapper,
      data OCTET STRING (SIZE(0..8))
   }

-- This is a dummy data type for interfaces on which can frames will be exchanged (between adapter and device through driver),
-- The driver is configured with option address=application-control-can-id and a passthrough packetizer.
-- This option enables a special case in the driver, in which messages should be treated as
-- buffers consisting of both the CAN ID and the CAN data. The mode is intended to be used with
-- externally defined protocols or hardware devices (e.g., CAN-TS, CANopen), and thus TASTE specific
-- message segmentation cannot be used, and so the payload must be at most 8 bytes long (CAN FD is not supported).
-- The type of parameter is ignored, Blackbox_C function sees this as a buffer with a given length.
-- The adapter, broker and driver use internally a sufficiently larger buffer,
-- so storing at most 12 bytes (4 for ID and at most 8 for data) is safe.
-- The size of ACN encoded value of this parameter shall be less than 8, otherwise the driver would assume that
-- message needs to be processed by Escaper, which is not supported together with address=application-control-can-id option.
-- If address=application-control-can-id was not selected, the type exchanged using a CAN port will be handled
-- in line with standard TASTE semantics, with proper escaping and segmentation, supporting large message sizes.
   Raw-Can-Frame ::= OCTET STRING (SIZE(12))

END
